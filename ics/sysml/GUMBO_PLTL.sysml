package GUMBO_PLTL {

    private import HAMR::*;

    language "GUMBO" /*{
        library
            functions
                def AGREE_Since(
                    a: Base_Types::Boolean,
                    b: Base_Types::Boolean,
                    prev_result: Base_Types::Boolean): Base_Types::Boolean :=
                    b or (a and prev_result);
    }*/
}
